LIEBERT-GP-REGISTRATION-MIB DEFINITIONS ::= BEGIN

IMPORTS
    MODULE-IDENTITY, OBJECT-IDENTITY, enterprises
        FROM SNMPv2-SMI
    ;

-- =============================================================================
-- Module Identification and Registration
-- =============================================================================

liebertGlobalProductsRegistrationModule MODULE-IDENTITY
  LAST-UPDATED "200710290000Z"
  ORGANIZATION "Liebert Corporation"
  CONTACT-INFO
      "Contact:   Technical Support

      Postal:
      Liebert Corporation
      1050 Dearborn Drive
      P.O. Box 29186
      Columbus OH, 43229
      US

      Tel: +1 (800) 222-5877

      E-mail: monitoring@emersonnetworkpower.com
      Web:    www.liebert.com

      Author:  John Stephen Sark"

   DESCRIPTION
      "The MIB module used to register Liebert SNMP OIDs.

      Copyright 2000-2004 Liebert Corporation. All rights reserved.
      Reproduction of this document is authorized on the condition
      that the forgoing copyright notice is included.

      This Specification is supplied 'AS IS' and Liebert Corporation
      makes no warranty, either express or implied, as to the use,
      operation, condition, or performance of the Specification."

   REVISION "200602220000Z"

   DESCRIPTION
    "Added support for Liebert DS Unit."

   ::= { liebertModuleReg 1 }

-- =============================================================================
-- Corporate OID identifiers for Emerson Electric and Liebert
-- =============================================================================

emerson OBJECT-IDENTITY
   STATUS      current
   DESCRIPTION "The enterprise registration for Emerson Electric Corporation."
   ::= { enterprises 476 }

liebertCorp OBJECT-IDENTITY
   STATUS      current
   DESCRIPTION "Liebert Corporation obtains it branch from Emerson Electric."
   ::= { emerson 1 }

-- =============================================================================
-- MAJOR branch for Liebert Corporation
-- Global Products branches all reside at this level in the MIB.
-- =============================================================================

liebertGlobalProducts OBJECT-IDENTITY
   STATUS      current
   DESCRIPTION "This branch is used for Liebert Global Products
               related information."
   REFERENCE   "All objects registered under this branch must be
               contained in this registration module."
   ::= { liebertCorp 42 }

-- =============================================================================
-- liebertGlobalProducts - Liebert Global Products Registrations
-- =============================================================================

lgpModuleReg OBJECT-IDENTITY
   STATUS      current
   DESCRIPTION "The Liebert Global Products MODULE-IDENTITY OIDs are
               registered via this branch."
   REFERENCE   "The Liebert MODULE-IDENTITYs are registered below in
               this registration module."
   ::= { liebertGlobalProducts 1 }

lgpAgent OBJECT-IDENTITY
   STATUS      current
   DESCRIPTION "All Liebert agent objects are registered in this branch."
   REFERENCE   "The registrations for the objects in this branch
               are defined below in a sub-section titled Liebert SNMP
               Agent - Registrations."
   ::= { liebertGlobalProducts 2 }

lgpFoundation OBJECT-IDENTITY
    STATUS      current
    DESCRIPTION "This branch is used to register Liebert objects that have
                common use across product families."
    REFERENCE   "The registrations for the objects in this branch
                are defined below in a sub-section titled Liebert Foundation
                Parameters - Registrations."
    ::= { liebertGlobalProducts 3 }

lgpProductSpecific OBJECT-IDENTITY
    STATUS      current
    DESCRIPTION "This branch is used to register Liebert product specific
                object identifiers."
    REFERENCE   "The registrations for the objects in this branch
                are defined below in a sub-section titled Liebert Product
                Specific - Registrations."
    ::= { liebertGlobalProducts 4 }

-- =============================================================================
-- lgpModuleReg - Liebert Module Identities
-- =============================================================================

liebertModuleReg OBJECT-IDENTITY
   STATUS      current
   DESCRIPTION "The Liebert Global Products MODULE-IDENTITY OIDs are
               registered via this branch."
   ::= { lgpModuleReg 1 }

liebertAgentModuleReg OBJECT-IDENTITY
   STATUS      current
   DESCRIPTION "The Liebert Global Products AGENT MODULE-IDENTITY OIDs are
               registered via this branch."
   ::= { lgpModuleReg 2 }

liebertConditionsModuleReg OBJECT-IDENTITY
   STATUS      current
   DESCRIPTION "The Liebert Global Products CONDITIONS MODULE-IDENTITY OIDs are
               registered via this branch."
   ::= { lgpModuleReg 3 }

liebertNotificationsModuleReg OBJECT-IDENTITY
   STATUS      current
   DESCRIPTION "The Liebert Global Products NOTIFICATIONS MODULE-IDENTITY OIDs
               are registered via this branch."
   ::= { lgpModuleReg 4 }

liebertEnvironmentalModuleReg OBJECT-IDENTITY
   STATUS      current
   DESCRIPTION "The Liebert Global Products ENVIRONMENTAL MODULE-IDENTITY OIDs
               are registered via this branch."
   ::= { lgpModuleReg 5 }

liebertPowerModuleReg OBJECT-IDENTITY
   STATUS      current
   DESCRIPTION "The Liebert Global Products POWER MODULE-IDENTITY OIDs are
               registered via this branch."
   ::= { lgpModuleReg 6 }

liebertControllerModuleReg OBJECT-IDENTITY
   STATUS      current
   DESCRIPTION "The Liebert Global Products CONTROLLER MODULE-IDENTITY OIDs are
               registered via this branch."
   ::= { lgpModuleReg 7 }

liebertSystemModuleReg OBJECT-IDENTITY
   STATUS      current
   DESCRIPTION "The Liebert Global Products SYSTEM MODULE-IDENTITY OIDs are
               registered via this branch."
   ::= { lgpModuleReg 8 }

-- =============================================================================
--  lgpAgent - Liebert SNMP Agent Registrations
-- =============================================================================

lgpAgentIdent OBJECT-IDENTITY
   STATUS      current
   DESCRIPTION "Liebert Agent Identification - This branch contains OIDS
               that are used to identify an agent and its managed device."
   REFERENCE   "All objects registered under this branch are implemented by
               the LIEBERT-GP-AGENT-MIB defined in the file
               LIEBERT_GP_AGENT.MIB."
    ::= { lgpAgent 1 }

lgpAgentNotifications OBJECT-IDENTITY
   STATUS      current
   DESCRIPTION "This branch is used to register Liebert agent notify object
               identifiers."
   REFERENCE   "All objects registered under this branch are implemented by
               the LIEBERT-GP-AGENT-MIB defined in the file
               LIEBERT_GP_AGENT.MIB."
    ::= { lgpAgent 3 }

lgpAgentDevice OBJECT-IDENTITY
   STATUS      current
   DESCRIPTION "This branch contains OIDs that are used to identify a
               managed device."
   REFERENCE   "All objects registered under this branch are implemented by
               the LIEBERT-GP-AGENT-MIB defined in the file
               LIEBERT_GP_AGENT.MIB."
    ::= { lgpAgent 4 }

lgpAgentControl OBJECT-IDENTITY
   STATUS      current
   DESCRIPTION "This branch contains objects relating to the control of
                the agent software."
   REFERENCE   "All objects registered under this branch are implemented by
               the LIEBERT-GP-AGENT-MIB defined in the file
               LIEBERT_GP_AGENT.MIB."
    ::= { lgpAgent 5 }

-- =============================================================================
-- lgpFoundation - Liebert Foundation Parameters Registrations
-- =============================================================================

lgpConditions OBJECT-IDENTITY
   STATUS      current
   DESCRIPTION "This branch is used to register Liebert status condition
               object identifiers."
   REFERENCE   "All objects registered under this branch are implemented by
               the LIEBERT-GP-CONDITIONS-MIB defined by the file
               LIEBERT_GP_COND.MIB."
    ::= { lgpFoundation 2 }

lgpNotifications OBJECT-IDENTITY
   STATUS      current
   DESCRIPTION "This branch is used to register Liebert notification object
               identifiers."
   REFERENCE   "All objects registered under this branch are implemented by
               the LIEBERT-GP-NOTIFICATIONS-MIB defined by the file
               LIEBERT_GP_NOTIFY.MIB."
    ::= { lgpFoundation 3 }

lgpEnvironmental OBJECT-IDENTITY
   STATUS      current
   DESCRIPTION "This branch is used to register Liebert environmental object
               identifiers."
   REFERENCE   "All objects registered under this branch are implemented by
               the LIEBERT-GP-ENVIRONMENTAL-MIB defined by the file
               LIEBERT_GP_ENV.MIB."
    ::= { lgpFoundation 4 }

lgpPower OBJECT-IDENTITY
   STATUS      current
   DESCRIPTION "This branch is used to register Liebert power object
               identifiers."
   REFERENCE   "All objects registered under this branch are implemented by
               the LIEBERT-GP-POWER-MIB defined by the file
               LIEBERT_GP_POWER.MIB."
    ::= { lgpFoundation 5 }

lgpController OBJECT-IDENTITY
   STATUS      current
   DESCRIPTION "This branch is used to register Liebert controller object
               identifiers."
   REFERENCE   "All objects registered under this branch are implemented by
               the LIEBERT-GP-CONTROLLER-MIB defined by the file
               LIEBERT_GP_CONTROLLER.MIB."
    ::= { lgpFoundation 6 }

lgpSystem OBJECT-IDENTITY
   STATUS      current
   DESCRIPTION "This branch is used to register Liebert system object
               identifiers."
   REFERENCE   "All objects registered under this branch are implemented by
               the LIEBERT-GP-SYSTEM-MIB defined by the file
               LIEBERT_GP_SYSTEM.MIB."
    ::= { lgpFoundation 7 }

-- =============================================================================
-- lgpProductSpecific - Liebert Product Specific Registrations
-- =============================================================================

lgpUpsProducts OBJECT-IDENTITY
   STATUS      current
   DESCRIPTION "This branch is used to register Liebert UPS object
               identifiers."
   REFERENCE   "The registrations for the objects in this branch are defined
               below in a sub-section titled Liebert UPS Registrations."
    ::= { lgpProductSpecific 2 }

lgpAcProducts OBJECT-IDENTITY
   STATUS      current
   DESCRIPTION "This branch is used to register Liebert Environmental object
               identifiers."
   REFERENCE   "The registrations for the objects in this branch
               are defined below in a sub-section titled Liebert Environmental
               Air Conditioning Registrations."
    ::= { lgpProductSpecific 3 }

lgpPowerConditioningProducts OBJECT-IDENTITY
   STATUS      current
   DESCRIPTION "This branch is used to register Liebert Power Distribution
                object identifiers."
   REFERENCE   "The registrations for the objects in this branch
               are defined below in a sub-section titled Liebert Power
               Conditioning Registrations."
    ::= { lgpProductSpecific 4 }

lgpTransferSwitchProducts OBJECT-IDENTITY
   STATUS      current
   DESCRIPTION "This branch is used to register Liebert Transfer Switch
                object identifiers."
   REFERENCE   "The registrations for the objects in this branch
               are defined below in a sub-section titled Liebert Transfer
               Switch Registrations."
    ::= { lgpProductSpecific 5 }

lgpMultiLinkProducts OBJECT-IDENTITY
   STATUS      current
   DESCRIPTION "This branch is used to register Liebert MultiLink object
               identifiers."
   REFERENCE   "The registrations for the objects in this branch
               are defined below in a sub-section titled
               Liebert MultiLink Registrations."
    ::= { lgpProductSpecific 7 }

-- =============================================================================
--  UpsProducts - Liebert UPS Registrations
-- =============================================================================

lgpSeries7200 OBJECT-IDENTITY
   STATUS      current
   DESCRIPTION "This branch is used to register Liebert Series 7200
               UPS product information."
   REFERENCE   "There are currently no objects registered under this branch."
    ::= { lgpUpsProducts 1 }

lgpUPStationGXT OBJECT-IDENTITY
   STATUS       current
   DESCRIPTION "This branch is used to register Liebert UPStationGXT UPS
                product information."
   REFERENCE   "There are currently no objects registered under this branch."
    ::= { lgpUpsProducts 2 }

lgpPowerSureInteractive OBJECT-IDENTITY
   STATUS       current
   DESCRIPTION "This branch is used to register Liebert PowerSure Interactive
               UPS product information."
   REFERENCE   "There are currently no objects registered under this branch."
    ::= { lgpUpsProducts 3 }

lgpNfinity OBJECT-IDENTITY
   STATUS       current
   DESCRIPTION "This branch is used to register Liebert Nfinity UPS
                product information."
   REFERENCE   "There are currently no objects registered under this branch."
    ::= { lgpUpsProducts 4 }

lgpNpower OBJECT-IDENTITY
   STATUS       current
   DESCRIPTION "This branch is used to register Liebert Npower UPS
                product information."
   REFERENCE   "There are currently no objects registered under this branch."
    ::= { lgpUpsProducts 5 }

lgpGXT2Dual OBJECT-IDENTITY
   STATUS       current
   DESCRIPTION "This branch is used to register Liebert GXT2 Dual Inverter
                product information."
   REFERENCE   "There are currently no objects registered under this branch."
    ::= { lgpUpsProducts 6 }

lgpPowerSureInteractive2 OBJECT-IDENTITY
   STATUS       current
   DESCRIPTION "This branch is used to register Liebert PowerSure Interactive 2
               UPS product information."
   REFERENCE   "There are currently no objects registered under this branch."
    ::= { lgpUpsProducts 7 }

lgpNX OBJECT-IDENTITY
   STATUS       current
   DESCRIPTION "This branch is used to register ENPC Nx UPS product
                information."
   REFERENCE   "There are currently no objects registered under this branch."
    ::= { lgpUpsProducts 8 }

lgpHiNet OBJECT-IDENTITY
   STATUS               current
   DESCRIPTION "This branch is used to register Hiross HiNet UPS product
                information."
   REFERENCE   "There are currently no objects registered under this branch."
    ::= { lgpUpsProducts 9 }

lgpSuper400 OBJECT-IDENTITY
   STATUS               current
   DESCRIPTION "This branch is used to register Super 400 UPS product
                information."
   REFERENCE   "There are currently no objects registered under this branch."
    ::= { lgpUpsProducts 11 }

lgpSeries600or610 OBJECT-IDENTITY
   STATUS               current
   DESCRIPTION "This branch is used to register the Liebert Series 600/610 UPS
                product information."
   REFERENCE   "There are currently no objects registered under this branch."
    ::= { lgpUpsProducts 12 }

lgpSeries300 OBJECT-IDENTITY
   STATUS               current
   DESCRIPTION "This branch is used to register the Liebert Series 300 UPS
                product information."
   REFERENCE   "There are currently no objects registered under this branch."
    ::= { lgpUpsProducts 13 }
    
lgpSeries610SMS OBJECT-IDENTITY
   STATUS               current
   DESCRIPTION "This branch is used to register the Liebert Series 610 Single
                Module System (SMS) UPS product information."
   REFERENCE   "There are currently no objects registered under this branch."
    ::= { lgpUpsProducts 14 }

lgpSeries610MMU OBJECT-IDENTITY
   STATUS               current
   DESCRIPTION "This branch is used to register the Liebert Series 610 Multi
                Module Unit (MMU) UPS product information."
   REFERENCE   "There are currently no objects registered under this branch."
    ::= { lgpUpsProducts 15 }

lgpSeries610SCC OBJECT-IDENTITY
   STATUS               current
   DESCRIPTION "This branch is used to register the Liebert Series 610 System
                Control Cabinet (SCC) UPS product information."
   REFERENCE   "There are currently no objects registered under this branch."
    ::= { lgpUpsProducts 16 }

-- =============================================================================
--  AcProducts - Liebert Environmental Air Conditioning Registrations
-- =============================================================================

lgpAdvancedMicroprocessor OBJECT-IDENTITY
   STATUS      current
   DESCRIPTION "This branch is used to register Liebert Environmental
               Advanced Microprocessor control information."
   REFERENCE   "There are currently no objects registered under this branch."
    ::= { lgpAcProducts 1 }

lgpStandardMicroprocessor OBJECT-IDENTITY
   STATUS      current
   DESCRIPTION "This branch is used to register Liebert Environmental
               Standard Microprocessor control information."
   REFERENCE   "There are currently no objects registered under this branch."
    ::= { lgpAcProducts 2 }

lgpMiniMate2 OBJECT-IDENTITY
   STATUS      current
   DESCRIPTION "This branch is used to register Liebert Environmental
               Mini-Mate 2 product information."
   REFERENCE   "There are currently no objects registered under this branch."
    ::= { lgpAcProducts 3 }

lgpHimod OBJECT-IDENTITY
   STATUS      current
   DESCRIPTION "This branch is used to register Liebert Environmental
               Himod product information."
   REFERENCE   "There are currently no objects registered under this branch."
    ::= { lgpAcProducts 4 }

lgpCEMS100orLECS15 OBJECT-IDENTITY
   STATUS      current
   DESCRIPTION "This branch is used to register Emerson Network Power Australia
               Environmental CEMS100 and LECS15 control information."
   REFERENCE   "There are currently no objects registered under this branch."
    ::= { lgpAcProducts 5 }

lgpIcom OBJECT-IDENTITY
   STATUS      current
   DESCRIPTION "This branch is used to register the Emerson Network Power
               Environmental iCOM control information."
   REFERENCE   "There are currently no objects registered under this branch."
    ::= { lgpAcProducts 6 }

-- =============================================================================
--  PowerConditioningProducts - Liebert Power Conditioning Registrations
-- =============================================================================

lgpPMP OBJECT-IDENTITY
   STATUS      current
   DESCRIPTION "This branch is used to register Liebert Power Distribution
               product information for the PMP (Power Monitoring Panel)
               product."
   REFERENCE   "There are currently no objects registered under this branch."
    ::= { lgpPowerConditioningProducts 1 }

lgpEPMP OBJECT-IDENTITY
   STATUS      current
   DESCRIPTION "This branch is used to register Liebert Power Distribution
               product information for the EPMP (Extended Power Monitoring
               Panel) product."
   REFERENCE   "There are currently no objects registered under this branch."
    ::= { lgpPowerConditioningProducts 2 }

-- =============================================================================
--  TransferSwitchProducts - Liebert Transfer Switch Registrations
-- =============================================================================

lgpStaticTransferSwitchEDS OBJECT-IDENTITY
   STATUS      current
   DESCRIPTION "This branch is used to register Liebert Transfer Switch
               product information for the EDS Static Transfer Switch product."
   REFERENCE   "There are currently no objects registered under this branch."
    ::= { lgpTransferSwitchProducts 1 }

lgpStaticTransferSwitch1 OBJECT-IDENTITY
   STATUS      current
   DESCRIPTION "This branch is used to register Liebert Transfer Switch
               product information for the Static Transfer Switch 1 product."
   REFERENCE   "There are currently no objects registered under this branch."
    ::= { lgpTransferSwitchProducts 2 }

lgpStaticTransferSwitch2 OBJECT-IDENTITY
   STATUS      current
   DESCRIPTION "This branch is used to register Liebert Transfer Switch
               product information for the Static Transfer Switch 2 product."
   REFERENCE   "There are currently no objects registered under this branch."
    ::= { lgpTransferSwitchProducts 3 }

-- =============================================================================
--  MultiLinkProducts - Liebert MultiLink Registrations
-- =============================================================================

lgpMultiLinkBasicNotification OBJECT-IDENTITY
   STATUS      current
   DESCRIPTION "This branch is used to register Liebert MultiLink
               MLBN device proxy information."
   REFERENCE   "There are currently no objects registered under this branch."
    ::= { lgpMultiLinkProducts 1 }

END
