LIEBERT-GP-NOTIFICATIONS-MIB DEFINITIONS ::= BEGIN

IMPORTS
    sysUpTime
        FROM RFC1213-MIB
    MODULE-IDENTITY, OBJECT-IDENTITY, NOTIFICATION-TYPE
        FROM SNMPv2-SMI
    lgpNotifications, liebertNotificationsModuleReg
        FROM LIEBERT-GP-REGISTRATION-MIB
    lgpConditionId, lgpConditionDescr, lgpConditionTime
        FROM LIEBERT-GP-CONDITIONS-MIB
   ;

-- =============================================================================
-- Module Identification and Registration
-- =============================================================================

liebertGlobalProductsNotificationsModule MODULE-IDENTITY
  LAST-UPDATED "200710290000Z"
  ORGANIZATION "Liebert Corporation"
  CONTACT-INFO
      "Contact:   Technical Support

      Postal:
      Liebert Corporation
      1050 Dearborn Drive
      P.O. Box 29186
      Columbus OH, 43229
      US

      Tel: +1 (800) 222-5877

      E-mail: monitoring@emersonnetworkpower.com
      Web:    www.liebert.com

      Author:  Craig S. Ward"

   DESCRIPTION
      "The MIB module used to register Liebert SNMP OIDs.

      Copyright 2000-2004 Liebert Corporation. All rights reserved.
      Reproduction of this document is authorized on the condition
      that the forgoing copyright notice is included.

      This Specification is supplied 'AS IS' and Liebert Corporation
      makes no warranty, either express or implied, as to the use,
      operation, condition, or performance of the Specification."

   REVISION "200608150000Z"

   DESCRIPTION
    "Added events for firmware update successful and for firmware corrupt."

   REVISION "200602220000Z"

   DESCRIPTION
    "Added support for Liebert DS Unit."

   ::= { liebertNotificationsModuleReg 1 }

-- =============================================================================
--  lgpNotifications - Liebert Notifications Registrations
-- =============================================================================

lgpEventNotifications OBJECT-IDENTITY
    STATUS current
    DESCRIPTION
        "Notifications for Liebert Global Products."
    ::= { lgpNotifications 0 }

lgpEventConditionEntryAdded NOTIFICATION-TYPE
    OBJECTS     { lgpConditionId, lgpConditionDescr, lgpConditionTime }
    STATUS      current
    DESCRIPTION
        "This notification is sent each time a condition is inserted into the
        conditions table."
    ::= { lgpEventNotifications 1 }

lgpEventConditionEntryRemoved NOTIFICATION-TYPE
    OBJECTS     { lgpConditionId, lgpConditionDescr, lgpConditionTime }
    STATUS      current
    DESCRIPTION
        "This notification is sent each time a condition is removed from the
        conditions table."
    ::= { lgpEventNotifications 2 }

lgpEventLowBatteryWarning NOTIFICATION-TYPE
    OBJECTS     { sysUpTime }
    STATUS      current
    DESCRIPTION
        "The battery's remaining charge is less than or equal to the agent's
        configured low threshold 'lgpPwrConfigLowBatteryWarningTime'."
    ::= { lgpEventNotifications 3 }

lgpEventLoadTransferedToBypass NOTIFICATION-TYPE
    OBJECTS     { sysUpTime }
    STATUS      current
    DESCRIPTION
        "The device has transfered the load to the bypass source."
    ::= { lgpEventNotifications 4 }

lgpEventInternalFault NOTIFICATION-TYPE
    OBJECTS     { sysUpTime }
    STATUS      current
    DESCRIPTION
        "The device has reported an internal fault."
    ::= { lgpEventNotifications 5 }

lgpEventBatteryTestFailed NOTIFICATION-TYPE
    OBJECTS     { sysUpTime }
    STATUS      current
    DESCRIPTION
        "The device has reported a battery self-test failure."
    ::= { lgpEventNotifications 6 }

lgpEventOutputOverload NOTIFICATION-TYPE
    OBJECTS     { sysUpTime }
    STATUS      current
    DESCRIPTION
        "The device has reported an output overload condition."
    ::= { lgpEventNotifications 7 }

lgpEventEstablishedPowerRedundancy NOTIFICATION-TYPE
    OBJECTS     { sysUpTime }
    STATUS      current
    DESCRIPTION
        "The device has transitioned to the user defined redundant state."
    ::= { lgpEventNotifications 8 }

lgpEventLostPowerRedundancy NOTIFICATION-TYPE
    OBJECTS     { sysUpTime }
    STATUS      current
    DESCRIPTION
        "The device as transitioned to a non-redundant power state as defined
        by the user configured threshold."
    ::= { lgpEventNotifications 9 }

lgpEventPowerModuleFailure NOTIFICATION-TYPE
    OBJECTS     { sysUpTime }
    STATUS      current
    DESCRIPTION
        "Device power module failure."
    ::= { lgpEventNotifications 10 }

lgpEventBatteryModuleFailure NOTIFICATION-TYPE
    OBJECTS     { sysUpTime }
    STATUS      current
    DESCRIPTION
        "Device battery module failure."
    ::= { lgpEventNotifications 11 }

lgpEventControlModuleFailure NOTIFICATION-TYPE
    OBJECTS     { sysUpTime }
    STATUS      current
    DESCRIPTION
        "Device control module failure."
    ::= { lgpEventNotifications 12 }

lgpEventPowerModuleWarning NOTIFICATION-TYPE
    OBJECTS     { sysUpTime }
    STATUS      current
    DESCRIPTION
        "Device power module warning."
    ::= { lgpEventNotifications 13 }

lgpEventBatteryModuleWarning NOTIFICATION-TYPE
    OBJECTS     { sysUpTime }
    STATUS      current
    DESCRIPTION
        "Device battery module warning."
    ::= { lgpEventNotifications 14 }

lgpEventControlModuleWarning NOTIFICATION-TYPE
    OBJECTS     { sysUpTime }
    STATUS      current
    DESCRIPTION
        "Device control module warning."
    ::= { lgpEventNotifications 15 }

lgpEventAgentFirmwareUpdateSuccessful NOTIFICATION-TYPE
    OBJECTS     { sysUpTime }
    STATUS      current
    DESCRIPTION
        "The firmware update to the agent card has completed successfully."
    ::= { lgpEventNotifications 16 }

lgpEventAgentFirmwareCorrupt NOTIFICATION-TYPE
    OBJECTS     { sysUpTime }
    STATUS      current
    DESCRIPTION
        "The firmware update to the agent card has failed and the firmware is
        now corrupt."
    ::= { lgpEventNotifications 17 }

END
